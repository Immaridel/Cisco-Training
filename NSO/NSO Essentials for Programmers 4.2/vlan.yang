module vlan {
  namespace "http://cisco.com/example/vlan";
  prefix vlan;

  import ietf-inet-types {
    prefix inet;
  }
  import tailf-ncs {
    prefix ncs;
  }

  import tailf-common {
    prefix tailf;
  }

  description "This is a VLAN service package.";
  revision 2024-06-25 {
    description
      "Initial revision.";
  }

  augment /ncs:services {
    list vlan {
      tailf:info "VLAN Service";
      key name;
      unique vlan-id;

      uses ncs:service-data;
      ncs:servicepoint "vlan";

      leaf name {
        tailf:info "Service Instance Name";
        type string;
      }

      leaf vlan-id {
        tailf:info "Unique VLAN ID";
        type uint32 {
          range "1..4096";
        }
      }

      list device {
        tailf:info "L3 Switch";
        key name;

        leaf name {
          tailf:info "Device Name";
          type leafref {
            path "/ncs:devices/ncs:device/ncs:name";
          }
        }
      }

      list interface {
        tailf:info "Ethernet Interface Type";
        key "intf-type intf-id";

        leaf intf-type {
          tailf:info "Ethernet Interface Type";
          type enumeration {
            enum Ethernet;
            enum FastEthernet;
            enum GigabitEthernet;
          }
        }

        leaf intf-id {
          tailf:info "Ethernet Interface ID";
          type string;
        }
      }
    
    }
  }
}
