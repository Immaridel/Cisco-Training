module l3vpn {
  namespace "http://cisco.com/example/l3vpn";
  prefix l3vpn;

  import ietf-inet-types {
    prefix inet;
  }
  import tailf-ncs {
    prefix ncs;
  }
  import tailf-common {
    prefix tailf;
  }

  augment /ncs:services {
    list l3vpn {
      key name;

      uses ncs:service-data;
      ncs:servicepoint "l3vpn";

      leaf vpn-name {
        tailf:info "Service Instance Name";
        type string;
      }

      leaf vpn-id {
        tailf:info "service Instance ID";
        type uint32 {
          range "10001..19999";
        }
      }

      leaf customer {
        tailf:info "VPN Customer";
        type leafref {
          path "/ncs:customers/ncs:customer/ncs:id";
        }
      }
    }
  }
}
