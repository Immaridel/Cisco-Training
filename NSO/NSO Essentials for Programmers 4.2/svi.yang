module svi {
  namespace "http://cisco.com/examples/svi";
  prefix svi;

  import ietf-inet-types {
    prefix inet;
  }
  import tailf-common {
    prefix tailf;
  }
  import tailf-ncs {
    prefix ncs;
  }

  description "This is SVI Python service package.";

  revision 2022-09-01 {
    description
      "Initial revision.";
  }

  augment /ncs:services {
    list svi {
      tailf:info "SVI Python Service";

      key name;
      leaf name {
        tailf:info "Unique service id";
        tailf:cli-allow-range;
        type string;
      }

      uses ncs:service-data;
      ncs:servicepoint svi-servicepoint;

      leaf vlan-id { 
        tailf:info "Unique VLAN ID"; 
        type uint32 { 
          range "1..4096"; 
        } 
      }

      list device {
        tailf:info "L3 Switch"; 
        key name; 

        leaf name { 
          tailf:info "Device Name"; 
          type leafref { 
            path "/ncs:devices/ncs:device/ncs:name"; 
          } 
        }

        leaf ip-prefix {
          tailf:info "Unique IPv4 Prefix for VLAN";
          type inet:ip-prefix;
        }

        list interface { 
          tailf:info "Ethernet Interface"; 
          key "intf-type intf-id"; 

          leaf intf-type { 
            tailf:info "Ethernet Interface Type"; 
            type enumeration { 
              enum Ethernet; 
              enum FastEthernet; 
              enum GigabitEthernet; 
            } 
          } 

          leaf intf-id { 
            tailf:info "Ethernet Interface ID"; 
            type string; 
          }
        }

      }

    }

  }
}
